module add-vpn-service {
  namespace "http://example.com/ns/yang/add-vpn-service";
  prefix vpn;

  import ietf-inet-types {
    prefix inet;
  }

  import tailf-ncs {
    prefix ncs;
  }

  import maintainers-base {
    prefix maintainers;
  }

  organization
    "EXAMPLE SYSTEMS";

  contact
    "EXAMPLE SYSTEMS
     Customer Service
     E-mail: example@example.com";

  description
    "L3VPN YANG Model.";

  revision 2021-10-15 {
    description
      "Initial revision";
  }

  typedef rdrt-type {
    type union {
      type string {
        pattern "[0-9]{1,5}:[0-9]{1,5}";
      }
      type enumeration {
        enum "65432:111";
        enum "65432:222";
      }
    }
  }

  identity IETSUNA {
    base maintainers:base-maintainers;
    description "The Member of Maintainers";
  }
  identity TSUNATOSHI {
    base maintainers:base-maintainers;
    description "The Member of Maintainers";
  }

  container vpn {
    description "L3vpn vrf";

    list vpn-policy {
      key "policy-name";
      description "VRF Configured Policy";

      uses ncs:service-data;
      ncs:servicepoint "add-vpn-service";

      leaf policy-name {
        type string;
      }

      leaf device {
        type leafref {
          path "/ncs:devices/ncs:device/ncs:name";
        }
        description "Configured Device Name";
      }

      leaf-list maintainer-members {
        type identityref {
          base maintainers:base-maintainers;
        }
        description "Maintainers of Customer";
      }

      container vrf {
        description "Vrf container";

        leaf vrf-name {
          type string;
          description "VRF Name";
        }

        leaf rd {
          type rdrt-type;
          description "Route Distinguisher and Route target";
        }

        leaf route-target-export {
          type rdrt-type;
          description "Route Target Export";
        }

        leaf-list route-target-import {
          type rdrt-type;
          description "Route Target Export";
        }
      }

      container loopback {
        description "Loopback container";

        leaf loopback-number {
          type uint16;
          description "Loopback Interface Number";
        }

        leaf loopback-ip {
          type inet:ipv4-address;
          description "Loopback IPv4 Address.";
        }
      }
    }
  }
}
